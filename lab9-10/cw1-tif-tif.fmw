FME workspace cw1-tif-tif.fmw

Parameters:
- DestDataset_TIFF =
- SourceDataset_GEODATABASE_FILE_RASTER_DATASET =
- SourceDataset_GEODATABASE_FILE_RASTER_DATASET_5 =
- SourceDataset_GEODATABASE_FILE_RASTER_DATASET_6 =
- SourceDataset_GEODATABASE_FILE_RASTER_DATASET_7 =
- SourceDataset_TIFF_3 =

Readers:
- TIFF_1: TIFF from $(SourceDataset_TIFF_3)
- GEODATABASE_FILE_RASTER_DATASET_1: GEODATABASE_FILE_RASTER_DATASET from $(SourceDataset_GEODATABASE_FILE_RASTER_DATASET)
- GEODATABASE_FILE_RASTER_DATASET_2: GEODATABASE_FILE_RASTER_DATASET from $(SourceDataset_GEODATABASE_FILE_RASTER_DATASET_5)
- GEODATABASE_FILE_RASTER_DATASET_3: GEODATABASE_FILE_RASTER_DATASET from $(SourceDataset_GEODATABASE_FILE_RASTER_DATASET_7)
- GEODATABASE_FILE_RASTER_DATASET_4: GEODATABASE_FILE_RASTER_DATASET from $(SourceDataset_GEODATABASE_FILE_RASTER_DATASET_6)

Writers:
- TIFF_2: TIFF to $(DestDataset_TIFF)

TIFF (reader TIFF_1)
    -> Reprojector
Reprojector
    DEST = LL-WGS84
    INTERPOLATION_TYPE_NAME = Nearest Neighbor
    RASTER_CELL_SIZE = Preserve Cells
    RASTER_TOLERANCE = 0.0
    REPROJECTED -> RasterPropertyExtractor
RasterPropertyExtractor
    -> AttributeCreator
AttributeCreator
    ATTR_TABLE = SET_TO absolute_path = $(FME_MF_DIR_ENCODED)data\ras250_gb\data\@Value(fme_basename).tif
    -> FilePropertyExtractor
FilePropertyExtractor
    FMT = FME Date/Time (%Y%m%d%H%M%S)
    PATH = @Value(absolute_path)
    -> AttributeCreator_2
AttributeCreator_2
    ATTR_TABLE = SET_TO NewName = @Value(fme_basename)_@Value(_file_size)
    -> TIFF (writer TIFF_2)
TIFF (writer TIFF_2)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- FMT =
- PATH =

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
