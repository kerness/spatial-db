FME workspace sentinel_downloader_fixed.fmw
Startup Python:
      # -*- coding: utf8 -*-
      import fme, smtplib, ssl
      from datetime import datetime


      # get the email and password from user parameters
      email = fme.macroValues['email']
      password = fme.macroValues['password']
      powiat = fme.macroValues['powiat']
      reciever_email = fme.macroValues['client_email']

      # timestamp
      now = datetime.now()
      timestamp = now.strftime("%d/%m/%Y %H:%M:%S")



      def send_email(sender_email, reciever_email, message ):
          # for SSL
          port = 465
          # SSL context
          context = ssl.create_default_context()

          with smtplib.SMTP_SSL("smtp.gmail.com", port, context=context) as server:
              server.login(email, password)
              server.sendmail(sender_email, reciever_email, message)



      message_content = """\
      Subject: Nowe przetwarzanie!

      Drogi uzytkowniku {0}, o godzinie {1} rozpoczeto przetwarzanie danych dla powiatu {2}."""
      message = message_content.format(reciever_email, timestamp, powiat)

      send_email(email, reciever_email, message,)
Shutdown Python:
      import fme, smtplib, ssl
      from datetime import datetime
      from email.mime.multipart import MIMEMultipart
      from email.mime.text import MIMEText
      from email.mime.application import MIMEApplication
      import os
      import json




      #get the email and password from user parameters
      email = fme.macroValues['email']
      password = fme.macroValues['password']
      powiat = fme.macroValues['powiat']
      reciever_email = fme.macroValues['client_email']
      start_date =  fme.macroValues['start_date']
      end_date =  fme.macroValues['end_date']
      cloud =  fme.macroValues['cloud']
      proc_duration = str(round(fme.elapsedRunTime, 0))


      # timestamp
      now = datetime.now()
      timestamp = now.strftime("%d/%m/%Y %H:%M:%S")


      def send_email(sender_email, reciever_email, message ):
          # for SSL
          port = 465
          # SSL context
          context = ssl.create_default_context()
          with smtplib.SMTP_SSL("smtp.gmail.com", port, context=context) as server:
              server.login(email, password)
              server.sendmail(sender_email, reciever_email, message)


      def create_log_file(powiat, start_date, end_date, cloud):
          dictionary = {
          "powiat" : powiat,
          "start_date" : start_date,
          "end_date"  : end_date,
          "colud_coverage" : cloud
          }
          json_log = json.dumps(dictionary, indent=4)
          with open(jsonPath, "w") as outfile:
              outfile.write(json_log)



      # prepare a message
      message = MIMEMultipart('mixed')
      message['From'] = 'Contact <{sender}>'.format(sender = email)
      message['To'] = reciever_email


      # paths
      file_name = powiat + r".tif"
      attachmentPath = os.path.join(r"C:\Users\kek\Desktop\SDB\cw11\res" , file_name)
      jsonPath = os.path.join(r"C:\Users\kek\Desktop\SDB\cw11\res" , "log.geojson")


      status = fme.status
      if status == 0: # if there is an error
          create_log_file(powiat, start_date, end_date, cloud)
          message['Subject'] = 'Przetwarzanie zakończone błędem!'

          msg_content = """

          <h3>Drogi uzytkowniku {0}, o godzinie {1} wystąpił błąd w przetwarzaniu danych dla powiatu {2}.</h3> <br>
          Prawdopodobny brak zobrazowań dla parametrów przesłąnych w załączniku.
          """.format(reciever_email, timestamp, powiat)
          body = MIMEText(msg_content, 'html')
          message.attach(body)
          try:
              with open(jsonPath, "rb") as attachment:
                  p = MIMEApplication(attachment.read(),_subtype="json")
                  p.add_header('Content-Disposition', "attachment; filename= %s" % jsonPath.split("\\")[-1])
                  message.attach(p)
          except Exception as e:
      	    print(str(e))

      else: # if everything is cool

          rast_mean =  round(fme.macroValues['mean'], 3)
          rast_stdev =  round(fme.macroValues['stdev'], 3)

          message['Subject'] = 'Przetwarzanie zakończone!'
          msg_content = """

          <h3>Drogi uzytkowniku {0}, o godzinie {1} zakonczone zostalo przetwarzanie danych dla powiatu {2}.</h3> <br>

          Czas trwania przetwarzania: {3} s
          Statystyki wynikowego rastra:
          <ul>
          <li>Średnia: {4}</li>
          <li>Odchylenie standardowe: {5}</li>
          </ul>
          Raster został przesłany w załączniku
          """.format(reciever_email, timestamp, powiat, proc_duration, str(rast_mean), str(rast_stdev))

          body = MIMEText(msg_content, 'html')
          message.attach(body)
          try:
              with open(attachmentPath, "rb") as attachment:
                  p = MIMEApplication(attachment.read(),_subtype="tif")
                  p.add_header('Content-Disposition', "attachment; filename= %s" % attachmentPath.split("\\")[-1])
                  message.attach(p)
          except Exception as e:
      	    print(str(e))

      print(proc_duration)
      # finally, send the message
      body = MIMEText(msg_content, 'html')
      send_email(email, reciever_email, message.as_string(),)

Parameters:
- DestDataset_GEOTIFF =
- SourceDataset_JPEG2000 =
- SourceDataset_JPEG2000_3 =
- client_email =
- cloud =
- email =
- end_date =
- password =
- powiat =
- start_date =

Readers:
- SHAPEFILE_1: SHAPEFILE from $(FME_MF_DIR)powiaty\Powiaty.shp
- JPEG2000_1: JPEG2000 from $(SourceDataset_JPEG2000)
- JPEG2000_2: JPEG2000 from $(SourceDataset_JPEG2000_3)

Writers:
- GEOTIFF_1: GEOTIFF to $(DestDataset_GEOTIFF)

Note: 4
JPEG2000 (reader JPEG2000_1)
    -> Reprojector_4
Reprojector_4
    DEST = LL84
    INTERPOLATION_TYPE_NAME = Nearest Neighbor
    RASTER_CELL_SIZE = Preserve Cells
    RASTER_TOLERANCE = 0.0
    REPROJECTED -> NDVICalculator [Red]
Note: 8
JPEG2000 (reader JPEG2000_2)
    -> Reprojector_3
Reprojector_3
    DEST = LL84
    INTERPOLATION_TYPE_NAME = Nearest Neighbor
    RASTER_CELL_SIZE = Preserve Cells
    RASTER_TOLERANCE = 0.0
    REPROJECTED -> NDVICalculator [Infrared]
NDVICalculator
    COLORIZE = Blue-Yellow-Green Palette
    INDEXTYPE = NDVI
    SAVIADJUSTMENT = 0.5
    -> Reprojector_2
Reprojector_2
    DEST = LL84
    INTERPOLATION_TYPE_NAME = Nearest Neighbor
    RASTER_CELL_SIZE = Preserve Cells
    RASTER_TOLERANCE = 0.0
    REPROJECTED -> Clipper [CLIPPEE]
Powiaty (reader SHAPEFILE_1)
    attributes: JPT_SJR_KO varchar(3), JPT_KOD_JE varchar(20), JPT_NAZWA_ varchar(128), JPT_ORGAN_ varchar(254), JPT_JOR_ID long, WERSJA_OD date, WERSJA_DO date, WAZNY_OD date, WAZNY_DO date, JPT_KOD__1 varchar(3), JPT_NAZWA1 varchar(3), JPT_ORGAN1 varchar(3), JPT_WAZNA_ varchar(3), ID_BUFORA_ double, ID_BUFORA1 double, ID_TECHNIC long, IIP_PRZEST varchar(20), IIP_IDENTY varchar(128), IIP_WERSJA varchar(32), JPT_KJ_IIP varchar(20), JPT_KJ_I_1 varchar(128), JPT_KJ_I_2 varchar(32), JPT_OPIS varchar(254), JPT_SPS_KO varchar(3), ID_BUFOR_1 long, JPT_ID long, JPT_KJ_I_3 varchar(3), Shape_Leng double, Shape_Area double
    -> Tester
Tester
    BOOL_OP = OR
    COMPOSITE_TEST = 1
    TEST_CLAUSE = CASE_INSENSITIVE_TEST @Value(JPT_NAZWA_) ENDS_WITH $(powiat)
    TEST_MODE = CASE_INSENSITIVE_TEST
    PASSED -> Reprojector
Reprojector
    DEST = LL84
    INTERPOLATION_TYPE_NAME = Nearest Neighbor
    RASTER_CELL_SIZE = Preserve Cells
    RASTER_TOLERANCE = 0.0
    REPROJECTED -> Clipper [CLIPPER]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterStatisticsCalculator
RasterStatisticsCalculator
    RASTER_LEVEL = BAND_ONLY
    RASTER_STATS = "0   MEAN   STDEV  "
    -> PythonCaller
PythonCaller
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.

              """
              FME_MacroValues['mean'] = feature.getAttribute('band0.mean')
              FME_MacroValues['stdev'] = feature.getAttribute('band0.stdev')


              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> test (writer GEOTIFF_1)
test (writer GEOTIFF_1)
    attributes: JPT_SJR_KO char(3), JPT_KOD_JE char(20), JPT_NAZWA_ char(128), JPT_ORGAN_ char(254), JPT_JOR_ID integer, WERSJA_OD date, WERSJA_DO date, WAZNY_OD date, WAZNY_DO date, JPT_KOD__1 char(3), JPT_NAZWA1 char(3), JPT_ORGAN1 char(3), JPT_WAZNA_ char(3), ID_BUFORA_ float, ID_BUFORA1 float, ID_TECHNIC integer, IIP_PRZEST char(20), IIP_IDENTY char(128), IIP_WERSJA char(32), JPT_KJ_IIP char(20), JPT_KJ_I_1 char(128), JPT_KJ_I_2 char(32), JPT_OPIS char(254), JPT_SPS_KO char(3), ID_BUFOR_1 integer, JPT_ID integer, JPT_KJ_I_3 char(3), Shape_Leng float, Shape_Area float
